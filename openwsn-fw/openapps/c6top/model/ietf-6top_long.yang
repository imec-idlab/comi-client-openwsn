module ietf-6top {

   namespace "http://6tisch.ietf.org/6top";

   prefix "ietf";

   description
   "Data model for the 6top sub-layer.";

   revision 2015-03-04 {
      description
      "v3 revision.";
   }

   typedef nodeaddresstype {
      type uint64;
      description
         "The type to store node address. It can be 64bits EUI address;
         or the short address defined by 6top, constrained by TSCH 
         macNodeAddress size, 2-octets. If using TSCH as MAC, the 
         higher 6-octets should be filled with 0, and lowest 2-octets 
         is neighbor short address";
   }
   
   list CellList {
         key "CellID";
         min-elements 1;
         unique "SlotframeID SlotOffset ChannelOffset";
         description
         "List of scheduled cells of a node with all of its neighbors,
         in all of its slotframes.";

         leaf CellID {
            type uint16;
            description
            "Equal to Linkhandle in the linkTable of TSCH";
            reference
            "IEEE802154e";
         }
         leaf SlotframeID {
            type leafref {
               path "/SlotframeList/SlotframeID";
            }
            description
            "SlotframeID, one in SlotframeList, indicates the slotframe
            the cell belongs to.";
            reference
            "IEEE802154e";
         }
         leaf SlotOffset {
            type uint16;
            description
            "Defined in IEEE802154e.";
            reference
            "IEEE802154e";
         }
         leaf ChannelOffset {
            type uint16;
            description
            "Defined in IEEE802154e. Value range is 0..15";
            reference
            "IEEE802154e";
         }
         leaf LinkOption {
            type bits {
               bit Transmit {
                  position 0;
               }
               bit Receive {
                  position 1;
               }
               bit Share {
                  position 2;
               }
               bit Timekeeping {
                  position 3;
               }
               bit Reserved1 {
                  position 4;
               }
               bit Reserved2 {
                  position 5;
               }
               bit Reserved3 {
                  position 6;
               }
               bit Reserved4 {
                  position 7;
               }
            }
            description
            "Defined in IEEE802154e.";
            reference
            "IEEE802154e";
         }
         leaf LinkType {
            type enumeration {
               enum NORMAL;
               enum ADVERTISING;
            }
            description
            "Defined in IEEE802154";
            reference
            "IEEE802154";
         }
         leaf CellType {
            type enumeration {
               enum SOFT;
               enum HARD;
            }
            description
            "Defined in 6top";
         }
         leaf NodeAddress {
            type nodeaddresstype;
            description
            "specify the target node address.";
         }        
         leaf TrackID {
            type leafref {
               path "/TrackList/TrackId";
            }
            description
            "A TrackID is one in the TrackList, pointing to a tuple
            (TrackOwnerAddr,InstanceID) , where TrackOwnerAddr is the
            address of the node which initializes the process of
            creating the track, i.e., the owner of the track; and
            InstanceID is an instance identifier given by the owner of
            the track.";
         }
         container Statistic {          
            leaf NumOfStatistic {
               mandatory true;
               type uint8;              
               description
               "Number of statistics collected on the cell";
            }
            list MeasureList {
               key "StatisticsMetricsID";
               min-elements 1;
               
               leaf StatisticsMetricsID{
                  type leafref {
                     path "/StatisticsMetricsList/StatisticsMetricsID";
                  }
                  description
                  "An index of StatisticsMetricList, which defines how
                  to collect data and get the statistice value";
               }
               leaf StatisticsValue{
                  type uint16;
                  config false;
                  description
                  "updated by 6top according to the statistics method
                  specified by StatisticsMetricsID";
               }
            }
         }
      }

   list SlotframeList {
      key "SlotframeID";
      min-elements 1;
      description
      "List of all of the slotframes used by the node.";

      leaf SlotframeID {
         mandatory true;
         type uint8;
         description
         "Equal to SlotframeHandle defined in TSCH";
         reference
         "IEEE802154e";
      }
      leaf NumOfSlots {
         mandatory true;
         type uint16 {
            range "1..max";
         }
         description
         "indicates how many timeslots in the slotframe";
      }
   }
   
   list Version {
      key "major minor";
      description
      "Provides a unique identification for the set of resources 
	  defined in this draft. Provides a major and minor version 
	  number that may be accessible independently";
      
	   leaf major {
         type uint8;
      }
      leaf minor {
         type uint8;
      }
    }

   list MonitoringStatusList {
         key "MonitoringStatusID";
         min-elements 1;
         unique "SlotframeID NodeAddress";
         description
         "List of the monitoring configuration and results per
         slotframe and neighbor. Basically, it is used for Monitoring
         Function of 6top to re-allocate softcells or initial the
         softcell negotiation process to increase/decrease number of
         softcells. Upper layer can use it also.";

         leaf MonitoringStatusID {
            type uint16;
         }
         leaf SlotframeID {
            type leafref {
               path "/SlotframeList/SlotframeID";
            }
            description
            "SlotframeID, one in SlotframeList, indicates the slotframe
            being monitored";
            reference
            "IEEE802154e";
         }
         leaf NodeAddress {
            type nodeaddresstype;
         }
         leaf EnforcePolicy {
            type enumeration {
               enum DISABLE;
               enum BESTEFFORT;
               enum STRICT;
               enum OVERPROVISION;           
            }
            default DISABLE;
            description
            "Currently enforced QoS policy. DISABLE-no QoS;
            BESTEFFORT- best effort policy is used; STRICT- Strict
            Priority Queueing; OVERPROVISION- cell overprovision";
         }
         leaf AllocatedHard {
            type uint16;
            config false;
            description
            "Number of hard cells allocated";
         }
         leaf AllocatedSoft {
            type uint16;
            config false;
            description
            "Number of soft cells allocated";
         }
         leaf OverProvision {
            type uint16;
            config false;
            must "../EnforcePolicy <> DISABLE ./";
            description
            "Overprovisioned cells. 0 if EnforcePolicy is
            DISABLE";
         }
         leaf QoS {
            type uint16;
            config false;
            description
            "Current QoS including overprovisioned cells, i.e. the
            bandwidth obtained including the overprovisioned cells.";
         }
         leaf NQoS {
            type uint16;
            config false;
            description
            "Real QoS without over provisioned cells, i.e. the actual
            bandwidth without taking into account the overprovisioned
            cells.";
         }
      }

   list StatisticsMetricsList {
      key "StatisticsMetricsID";
      min-elements 1;
      unique "SlotframeID SlotOffset ChannelOffset NodeAddress";
      description
      "List of Statistics Metrics used in the node.";

      leaf StatisticsMetricsID {
         type uint16;
      }
      leaf SlotframeID {
         type leafref {
            path "/SlotframeList/SlotframeID";
         }
         description
         "SlotframeID, one in SlotframeList, specifies the slotframe to
         which the statistics metrics applies to. If empty, applies to
         all slotframes";
         reference
         "IEEE802154e";
      }
      leaf SlotOffset {
         type uint16;
         description
         "Specific slotOffset to which the statistics metrics applies
         to. If empty, applies to all timeslots";
         reference
         "IEEE802154e";
      }
      leaf ChannelOffset {
         type uint16;
         description
         "Specific channelOffset to which the statistics metrics applies
         to. If empty, applies to all channels";
         reference
         "IEEE802154e";
      }
      
      leaf NodeAddress {
         type nodeaddresstype;
         description
         "If NodeAddress is empty, applies to all neighbor nodes.";
      }
      
      leaf Metrics {
      type enumeration {
		   enum macCounterOctets;
         enum macRetryCount;
		   enum macMultipleRetryCount; 
		   enum macTXFailCount; 
		   enum macTXSuccessCount; 
		   enum macFCSErrorCount; 
		   enum macSecurityFailure; 
		   enum macDuplicateFrameCount; 
		   enum macRXSuccessCount; 
		   enum macNACKcount; 
         enum PDR;
         enum ETX;
         enum RSSI;
         enum LQI;		 
      }
      description
      "The metric to be monitored. Include those provided by underlying 
	  IEEE 802.15.4e TSCH -- see table 4i (2012). 
	  PDR,ETX,RSSI,LQI are maintained by 6top. ";
      }
      leaf Window {
         type uint16;
         description
         "measurement period, in Number of the slotframe size";
      }
      leaf Enable {
         type enumeration {
            enum DISABLE;
            enum ENABLE;
         }
         default DISABLE;
         description
         "indicates the StatisticsMetric is active or not";
      }
   }

   list EBList {
         key "EbID";
         min-elements 1;
         description
         "List of information related with the EBs used by the node";

         leaf EbID {
            type uint8;
         }
         leaf CellID {
            type leafref {
               path "/CellList/CellID";
            }
            description
            "CellID, one in CellList, indicates the cell used to send
            EB";
         }
         leaf Peroid {
            type uint16;
            description
            "The EBs period, in seconds, indicates the interval between
            two EB sendings";
         }
         leaf Expiration {
            type enumeration {
               enum NEVERSTOP;
               enum EXPIRATION;
            }
            description
            "NEVERSTOP- the period of the EB never stops; EXPIRATION-
            when the Period arrives, the EB will stop.";
         }
         leaf Priority {
            type uint8;
            description
            "The joining priority model that will be used for
            advertisements. Joining priority MAY be for example
            SAME_AS_PARENT, RANDOM, BEST_PARENT+1 or
            DAGRANK(rank).";
         }
      }

   container TimeSource {
      description
      "specify the timesource selection policy and some relative
      statistics. ";

      leaf policy {
         type enumeration {
            enum ALLPARENT;
            enum BESTCONNECTED;
            enum LOWESTJOINPRIORITY;
         }
         default LOWESTJOINPRIORITY;
         description
         "indicates the policy to choose timesource. ALLPARENT- choose
         from all parents; BESTCONNECTED- choose the best-connected
         node; LOWESTJOINPRIORITY- choose the node with lowest priority
         in its EB.";
      }
            
      leaf NodeAddress {
         type nodeaddresstype;
         description
         "Specifies the address of selected time source neighbors.";
      }
      
      leaf MinTimeCorrection {
         type uint16;
         config false;
         description
         "measured in microsecond";
      }
      leaf MaxTimeCorrection {
         type uint16;
         config false;
         description
         "measured in microsecond";
      }
      leaf AveTimeCorrection {
         type uint16;
         config false;
         description
         "measured and computed in microsecond";
      }
   }

   typedef asntype {
      description
         "The type to store ASN. String of 5 bytes";
      type string {
         length "0..5";
      }
   }

   list NeighborList {
      key "NodeAddress";
      description
      "statistics per communication link. ";

      leaf NodeAddress {
         type nodeaddresstype;
         description
         "Specifies the address of the neighbor.";
      }
      
      leaf RSSI {
         type uint8;
         config false;
         description
         "The received signal strength";
      }
      leaf LinkQuality {
         type uint8;
         config false;
         description
         "The LQI metric";
      }
      leaf ASN {
         type asntype;
         config false;
         description
         "The 5 ASN bytes, indicates the most recent timeslot when a
         packet from the neighbor was received";
      }
   }

   list QueueList {
      key "QueueId";
      min-elements 1;
      description
      "List of Queues, including configuration and statistics.";

      leaf QueueId {
         type uint8;
         description
         "Queue Identifier";
      }
      leaf TxqLength {
         type uint8;
         description
         "The TX queue length in number of packets";
      }
      leaf RxqLength {
         type uint8;
         description
         "The RX queue length in number of packets";
      }
      leaf NumrTx {
         type uint8;
         description
         "Number of allowed retransmissions.";
      }
      leaf Age {
         type uint16;
         description
         "In seconds. Discard packet according to its age
          on the queue. 0 if no discards are allowed.";
      }
      leaf RTXbackoff {
         type uint8;
         description
         "retransmission backoff in number of slotframes.
          0 if next available timeslot wants to be used.";
      }
      leaf StatsWindow {
         type uint16;
         description
         "In second, window of time used to compute stats.";
      }
      leaf QueuePriority {
         type uint8;
         description
         "The priority for this queue.";
      }
      list TrackIds {
         key "TrackID";
         leaf TrackID{
            type leafref {
               path "/TrackList/TrackId";
            }
            description
            "The TrackID, one in TrackList, indicates the Track is
            associated with the Queue.";
         }
      }
      leaf MinLenTXQueue {
         type uint8;
         config false;
         description
         "Statistics, lowest TX queue length registered in the window.";
      }
      leaf MaxLenTXQueue {
         type uint8;
         config false;
         description
         "Statistics, largest TX queue length registered in the
         window.";
      }
      leaf AvgLenTXQueue {
         type uint8;
         config false;
         description
         "Statistics, avg TX queue length registered in the window.";
      }
      leaf MinLenRXQueue {
         type uint8;
         config false;
         description
         "Statistics, lowest RX queue length registered in the window.";
      }
      leaf MaxLenRXQueue {
         type uint8;
         config false;
         description
         "Statistics, largest RX queue len registered in the window.";
      }
      leaf AvgLenRXQueue {
         type uint8;
         config false;
         description
         "Statistics, avg RX queue length registered in the window.";
      }
      leaf MinRetransmissions {
         type uint8;
         config false;
         description
         "Statistics, lowest number of retransmissions registered in
         the window.";
      }
      leaf MaxRetransmissions {
         type uint8;
         config false;
         description
         "Statistics, largest number of retransmissions registered
          in the window.";
      }
      leaf AvgRetransmissions {
         type uint8;
         config false;
         description
         "Statistics, average number of retransmissions registered
          in the window.";
      }
      leaf MinPacketAge {
         type uint16;
         config false;
         description
         "Statistics, in seconds, minimum time a packet stayed in
          the queue during the observed window.";
      }
      leaf MaxPacketAge {
         type uint16;
         config false;
         description
         "Statistics, in seconds, maximum time a packet stayed
          in the queue during the observed window.";
      }
      leaf AvgPacketAge {
         type uint16;
         config false;
         description
         "Statistics, in seconds, average time a packet stayed in
          the queue during the observed window.";
      }
      leaf MinBackoff {
         type uint8;
         config false;
         description
         "Statistics, in number of slotframes, minimum Backoff
          for a packet in the queue during the observed window.";
      }
      leaf MaxBackoff {
         type uint8;
         config false;
         description
         "Statistics, in number of slotframes, maximum Backoff
          for a packet in the queue during the observed window.";
      }
      leaf AvgBackoff {
         type uint8;
         config false;
         description
         "Statistics, in number of slotframes, average Backoff
          for a packet in the queue during the observed window.";
      }
   }

   list LabelSwitchList {
      key "LabelSwitchID";
      description
      "List of Label switch' configuration on the node";

      leaf LabelSwitchID {
         type uint16;
      }
      list InputCellIds {
         key "CellID";
         leaf CellID{
            type leafref {
               path "/CellList/CellID";
            }
            description
            "The CellID, indicates the Rx cell on which the packet will
            come in.";
         }
      }
      list OutputCellIds {
         key "CellID";
         leaf CellID{
            type leafref {
               path "/CellList/CellID";
            }
            description
            "The CellID, indicates the Tx cell on which the received
            packet should be sent out.";
         }
      }
      leaf LoadBalancingPolicy {
         type enumeration {
            enum ROUNDROBIN;
            enum OTHER;
         }
         description
         "The load-balancing policy. ROUNDROBIN- Round robin algorithm
         is used for forwarding scheduling.";
      }
   }

   list TrackList {
      key "TrackId";
      min-elements 1;
      unique "TrackOwnerAddr InstanceID";
      description
      "List of the tracks through the node. At lease the best effort 
      track is existing";

      leaf TrackId {
         type uint16;
         description
         "Track Identifier, named locally. It is used to refer to the
         tuple (TrackOwnerAddr, InstanceID).";
      }
      leaf TrackOwnerAddr {
         type uint64;
         description
         "The address of the node which initializes the process of
         creating the track, i.e., the owner of the track;";
      }
      leaf InstanceID {
         type uint16;
         description
         "InstanceID is an instance identifier given by the owner of
         the track. InstanceID comes from upper layer; InstanceID could
         for example be the local instance ID defined in RPL.";
      }
   }

   list ChunkList {
            key "ChunkId";
            description
            "List of the chunks assigned to the node.";

            leaf ChunkId{
               type uint16;
               description
               "The identifier of a chunk";
            }
            leaf SlotframeId{
               type leafref {
                  path "/SlotframeList/SlotframeID";
               }
               description
               "SlotframeID, one in SlotframeList, indicates the
               slotframe to which the chunk belongs";
            }
            leaf SlotBase {
               type uint16;
               description
               "the base slotOffset of the chunk in the slotframe";
            }
            leaf SlotStep {
               type uint8;
               description
               "the slot incremental of the chunk";
            }
            leaf ChannelBase {
               type uint16;
               description
               "the base channelOffset of the chunk";
            }
            leaf ChannelStep {
               type uint8;
               description
               "the channel incremental of the chunk";
            }
            leaf ChunkSize {
               type uint8;
               description
               "the number of cells in the chunk. The chunk is the set
               of (slotOffset(i), channelOffset(i)),
               i=0..Chunksize-1,
               slotOffset(i)= (slotBase + i * slotStep) % slotframeLen,
               channelOffset(i) = (channelBase + i * channelStep) % 16";
            }
         }

   list ChunkCellList {
            key "SlotOffset ChannelOffset";
            description
            "List of all of the cells assigned to the node via the
            assignment of chunks.";

            leaf SlotOffset{
               type uint16;
               description
               "The slotoffset of a cell which belongs to a Chunk";
            }
            leaf ChannelOffset{
               type uint16;
               description
               "The channeloffset of a cell which belongs to a chunk.";
            }
            leaf ChunkId {
               type leafref{
                  path "/ChunkList/ChunkId";
               }
               description
               "Identifier of the chunk the cell belongs to";
            }
            leaf CellID{
               type leafref {
                  path "/CellList/CellID";
               }
               description
               "Initial value of CellID is 0xFFFF. When the cell is
               scheduled, the value of CellID is same as that in
               CellList";
            }
            leaf ChunkCellStatus {
               type enumeration {
                  enum UNSCHEDULED;
                  enum SCHEDULED;
               }
            }
         }

   container TSCHSpecificPIBAttributes {
               description
               "TSCH specific MAC PIB attributes.";
               reference
               "table 52b in IEEE802.15.4e-2012.";

               leaf macMinBE {
                  type uint8;
                  description
                  "defined in Table 52b of IEEE802.15.4e-2012,
                  The minimum value of the backoff exponent (BE) in the
                  CSMA-CA algorithm or the TSCH-CA algorithm. default:
                  3-CSMA-CA, 1-TSCH-CA";
               }
               leaf macMaxBE {
                  type uint8;
                  description
                  "defined in Table 52b of IEEE802.15.4e-2012,
                  The maximum value of the backoff exponent (BE) in the
                  CSMA-CA algorithm or the TSCH-CA algorithm. default:
                  5-CSMA-CA, 7-TSCH-CA";
               }
               leaf macDisconnectTime {
                  type uint16;
                  description
                  "defined in Table 52b of IEEE802.15.4e-2012,
                  Time (in Timeslots) to send out Disassociate frames
                  before disconnecting, default: 0x00ff";
               }
               leaf macJoinPriority {
                  type uint8;
                  description
                  "defined in Table 52b of IEEE802.15.4e-2012,
                  The lowest join priority from the TSCH Synchronization
                  IE in an Enhanced beacon, default: 1";
               }
               leaf macASN {
                  type asntype;
                  description
                  "defined in Table 52b of IEEE802.15.4e-2012,
                  The Absolute Slot Number, i.e., the number of slots
                  that ha elapsed since the start of the network.";
               }
               leaf macNoHLBuffers {
                  type enumeration {
                     enum TRUE;
                     enum FALSE;
                  }
                  description
                  "defined in Table 52b of IEEE802.15.4e-2012,
                  If the value is TRUE, the higher layer receiving the
                  frame payload cannot buffer it, and the device should
                  acknowledge frames with a NACK; If FALSE, the higher
                  layer can accept the frame payload. default: FALSE";
               }
            }

   list TSCHmacTimeslotTemplate {
               key "macTimeslotTemplateId";
               min-elements 1;
               description
               "List of all timeslot templates used in the node.";
               reference
               "table 52e in IEEE802.15.4e-2012.";

               leaf macTimeslotTemplateId {
                  type uint8;
                  description
                  "defined in Table 52e of IEEE802.15.4e-2012.
                  Identifier of Timeslot Template. default: 0";
               }
               leaf macTsCCAOffset {
                  type uint16;
                  description
                  "The time between the beginning of timeslot and start
                  of CCA operation, in microsecond. default: 1800";
               }
               leaf macTsCCA {
                  type uint16;
                  description
                  "Duration of CCA, in microsecond. default: 128";
               }
               leaf macTsTxOffset {
                  type uint16;
                  description
                  "The time between the beginning of the timeslot and
                  the start of frame transmission, in microsecond.
                  default: 2120";
               }
               leaf macTsRxOffset {
                  type uint16;
                  description
                  "Beginning of the timeslot to when the receiver shall
                  be listening, in microsecond. default: 1120";
               }
               leaf macTsRxAckDelay {
                  type uint16;
                  description
                  "End of frame to when the transmitter shall listen for
                  Acknowledgment, in microsecond. default: 800";
               }
               leaf macTsTxAckDelay {
                  type uint16;
                  description
                  "End of frame to start of Acknowledgment, in
                  microsecond.
                  default: 1000";
               }
               leaf macTsRxWait {
                  type uint16;
                  description
                  "The time to wait for start of frame, in microsecond.
                  default: 2200";
               }
               leaf macTsAckWait {
                  type uint16;
                  description
                  "The minimum time to wait for start of an
                  Acknowledgment, in microsecond. default: 400";
               }
               leaf macTsRxTx {
                  type uint16;
                  description
                  "Transmit to Receive turnaround, in microsecond.
                  default: 192";
               }
               leaf macTsMaxAck {
                  type uint16;
                  description
                  "Transmission time to send Acknowledgment,in
                  microsecond. default: 2400";
               }
               leaf macTsMaxTx {
                  type uint16;
                  description
                  "Transmission time to send the maximum length frame,
                  in microsecond. default: 4256";
               }
               leaf macTsTimeslotLength {
                  type uint16;
                  description
                  "The total length of the timeslot including any unused
                  time after frame transmission and Acknowledgment,
                  in microsecond. default: 10000";
               }
            }

   list TSCHHoppingSequence {
               key "macHoppingSequenceID";
               min-elements 1;
               description
               "List of all channel hopping sequences used in the
               nodes";
               reference
               "Table 52f of IEEE802.15.4e-2012";

               leaf macHoppingSequenceID {
                  type uint8;
                  description
                  "defined in Table 52f of IEEE802.15.4e-2012.
                  Each hopping sequence has a unique ID. default: 0";
               }
               leaf macChannelPage {
                  type uint8;
                  description
                  "Corresponds to the 5 MSBs (b27, ..., b31) of a row
                  in phyChannelsSupported. Note this may not correspond
                  to the current channelPage in use.";
               }
               leaf macNumberOfChannels {
                  type uint16;
                  description
                  "Number of channels supported by the PHY on this
                  channelPage.";
               }
               leaf macPhyConfiguration {
                  type uint32;
                  description
                  "For channel pages 0 to 6, the 27 LSBs(b0, b1, ...,
                  b26) indicate the status (1 = to be used, 0 = not to
                  be used) for each of the up to 27 valid channels
                  available to the PHY. For pages 7 and 8, the 27 LSBs
                  indicate the configuration of the PHY, and the channel
                  list is contained in the extendedBitmap.";
               }
               leaf macExtendedBitmap {
                  type uint64;
                  description
                  "For pages 7 and 8, a bitmap of numberOfChannels bits,
                  where bk shall indicate the status of channel k for
                  each of the up to numberOfChannels valid channels
                  supported by that channel page and phyConfiguration.
                  Otherwise field is empty.";
               }
               leaf macHoppingSequenceLength {
                  type uint16;
                  description
                  "The number of channels in the Hopping Sequence.
                  Does not necessarily equal numberOfChannels.";
               }
               list macHoppingSequenceList {
                  key "HoppingChannelID";
                  leaf HoppingChannelID {
                     type uint16;
                     description
                     "channels to be hopped over";
                  }
               }
               leaf macCurrentHop {
                  type uint16;
                  config false;
                  description
                  "Index of the current position in the hopping sequence
                  list.";
               }
            }
            
   container SecurityAttributes{      
         leaf SecurityMode {
            type enumeration {
                  enum NO_SECURITY;
                  enum NETWORK_WIDE_MIC;
                  enum NETWORK_WIDE_DHE_PSK; 
                  enum NETWORK_WIDE_IKE2_PSK; 
                  enum PK_DTLS_ECDSA; 
                  enum PK_IKEv2_ECDSA; 
                  enum OTHER; 
            }
            description
             "The security mode is to be used.";
         }

         leaf-list Certificate{
            type uint8;
            min-elements 128;
            description "A list of bytes for the certificate ECDSA PKIX or PSK";
         }
         
         leaf DevID {
            type enumeration {
                 enum IDevID;
                 enum LDevID;
            }
            description " indicate the feature of DevID.";        
         }
         
         leaf-list PSK{
            type uint8;
            min-elements 128;
            description "A list of bytes for the PSK while using PSK
                        method";
         }
         
         leaf PanID {
            type uint16;
            description "2 Bytes the network PANID";
         }

         leaf JoinAssistant {
            type enumeration {
                 enum TRUE;
                 enum FALSE;
            }
            description "a toggle which enables a node to 
                         become a join assistant.";        
         }

         leaf-list ULA{
            type uint8;
            min-elements 16;
            description "A ULA to be announced in the RA for joining nodes. 
            It is 128bits+prefixlen.  A device with multiple interfaces 
            should configure different 64-bit prefixes.";
         }
         
         leaf BeaconWellKnownKey{
            type string; 
            default "6TISCHJOIN";
            description "the well known beacon key";
         }
        
        leaf-list JCEAddress{
            type uint8;
            min-elements 8;
            description "the address of the JCE, for the ACL about 
                         who can contact joining nodes.";
        }
      }
   }
